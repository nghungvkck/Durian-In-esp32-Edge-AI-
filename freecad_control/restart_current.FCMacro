"""Open current D36 before reconnecting; never replay interrupted requests."""
from pathlib import Path
import FreeCAD as App
root=Path(r'D:\Hoc_tap_Sinh_Vien\Kien_thu_AI\Project\Duration_edge_ai')
App.openDocument(str(root/'3D/Enclosure_Compact_Layout_D36/Printed_Retention_35x25x6/D36_Printed_Retention_35x25x6.FCStd'))
bridge=root/'freecad_control/easy_insert_session/Connect.FCMacro'
exec(compile(bridge.read_text(encoding='utf-8'),str(bridge),'exec'))
